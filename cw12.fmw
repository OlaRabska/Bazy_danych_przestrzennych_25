FME workspace cw12.fmw

Parameters:
- SourceDataset_SHAPEFILE = E:\studia\Semestr 5\Bazy danych przestrzennych\Cwiczenia 3\T2019_KAR_GERMANY\T2019_KAR_POI_TABLE.shp   # Source Esri Shapefile(s)
- SourceDataset_SHAPEFILE_5 = E:\studia\Semestr 5\Bazy danych przestrzennych\Cwiczenia 3\T2019_KAR_GERMANY\T2019_KAR_STREETS.shp   # Source Esri Shapefile(s)
- SourceDataset_SHAPEFILE_7 = E:\studia\Semestr 5\Bazy danych przestrzennych\Cwiczenia 3\T2019_KAR_GERMANY\T2019_KAR_STREET_NODE.shp   # Source Esri Shapefile(s)
- SourceDataset_CSV2 = $(FME_MF_DIR)route_points.csv   # Source CSV (Comma Separated Value) File(s)
- DestDataset_GEOJSON_3 = $(FME_MF_DIR)poi_route_B.json   # Destination GeoJSON File
- DestDataset_GEOJSON = $(FME_MF_DIR)poi_route_A.json   # Destination GeoJSON File
- DestDataset_GEODATABASE_FILE_3 = $(FME_MF_DIR)cw12.gdb   # File Geodatabase
- DestDataset_GEODATABASE_FILE = $(FME_MF_DIR)cw12.gdb   # File Geodatabase

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_7)
- CSV2_1: CSV2 from $(SourceDataset_CSV2)

Writers:
- GEOJSON_1: GEOJSON to $(DestDataset_GEOJSON)
- GEOJSON_2: GEOJSON to $(DestDataset_GEOJSON_3)
- GEODATABASE_FILE_1: GEODATABASE_FILE to $(DestDataset_GEODATABASE_FILE)
- GEODATABASE_FILE_2: GEODATABASE_FILE to $(DestDataset_GEODATABASE_FILE_3)

T2019_KAR_POI_TABLE (reader SHAPEFILE_1)
    attributes: POI_ID long, LINK_ID long, TYPE varchar(250), POI_NAME varchar(250), ST_NAME varchar(250), LAT number(31,15), LON number(31,15)
    -> Reprojector
Reprojector
    DEST = DHDN.Berlin/Cassini
    INTERPOLATION_TYPE = NearestNeighbor
    RASTER_CELL_SIZE = PreserveCells
    RASTER_TOLERANCE = 0.0
    REPROJECTED -> SpatialFilter [Candidate]
    REPROJECTED -> SpatialFilter_2 [Candidate]
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_2
Reprojector_2
    DEST = DHDN.Berlin/Cassini
    INTERPOLATION_TYPE = NearestNeighbor
    RASTER_CELL_SIZE = PreserveCells
    RASTER_TOLERANCE = 0.0
    REPROJECTED -> ShortestPathFinder [NETWORK]
    REPROJECTED -> Tester
    REPROJECTED -> Tester_2
    REPROJECTED -> Tester_3
Tester
    BOOL_OP = OR
    TEST_CLAUSE = TEST @Value(DIR_TRAVEL) = B
    TEST_MODE = TEST
    PASSED -> AttributeManager
    FAILED -> AttributeManager_2
Tester_2
    BOOL_OP = OR
    TEST_CLAUSE = TEST @Value(DIR_TRAVEL) = F
    TEST_MODE = TEST
    PASSED -> AttributeManager
    FAILED -> AttributeManager_2
Tester_3
    BOOL_OP = OR
    TEST_CLAUSE = TEST @Value(DIR_TRAVEL) = T
    TEST_MODE = TEST
    PASSED -> AttributeManager
    FAILED -> AttributeManager_2
AttributeManager
    ATTR_TABLE:
      SET_TO forwardCost (uint8) = 1
      SET_TO reverseCost (uint16) = 9999
    -> ShortestPathFinder_2 [NETWORK]
AttributeManager_2
    ATTR_TABLE:
      SET_TO forwardCost (uint8) = 1
      SET_TO reverseCost (varchar(200))
      SET_TO = 1
    -> ShortestPathFinder_2 [NETWORK]
CSV (reader CSV2_1)
    attributes: id varchar(5), lon real32, lat real32
    -> VertexCreator
VertexCreator
    COORDSYS = LL-WGS84
    MEASURE_TYPE_LOOKUP = CONTINUOUS
    MODE = REPLACE
    REMOVE_ATTRIBUTES = No
    XVAL = @Value(lon)
    YVAL = @Value(lat)
    MEASURE_TYPE = Continuous
    MODE_NAME = Replace with Point
    -> CoordinateSystemSetter
CoordinateSystemSetter
    COORDSYS = LL-WGS84
    -> LineBuilder
LineBuilder
    ACCUM_INPUT_ATTRS_LOOKUP = All
    REMOVE_DUPLICATES_LOOKUP = NO
    ACCUM_INPUT_ATTRS = Merge Incoming Attributes
    REMOVE_DUPLICATES = No
    LINE -> Reprojector_4
Reprojector_4
    DEST = DHDN.Berlin/Cassini
    INTERPOLATION_TYPE = NearestNeighbor
    RASTER_CELL_SIZE = PreserveCells
    RASTER_TOLERANCE = 0.0
    REPROJECTED -> ShortestPathFinder [FROM-TO]
    REPROJECTED -> ShortestPathFinder_2 [FROM-TO]
    REPROJECTED -> Inspector_3
ShortestPathFinder
    ALLOW_UTURNS = Yes
    REORDER_MODE = NONE
    SNAP_POINTS = Yes
    SNAP_TOLERANCE = 200
    THREE_D = No
    WEIGHT_ATTR_CHOICE = BY_LENGTH
    PATH -> Inspector
    PATH -> Bufferer
    PATH -> SpatialFilter_3 [Filter]
    PATH -> LengthCalculator
Inspector
Bufferer
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> poi_route_A (writer GEOJSON_1)
poi_route_A (writer GEOJSON_1)
    attributes: id string, lon float, lat float, _total_cost string, POI_ID int, LINK_ID int, TYPE string, POI_NAME string, ST_NAME string, LAT string, LON string, _predicate string
LengthCalculator
    DIM = 2
    LEN_ATTR = _length
    MULT = 1
    -> AttributeManager_6
AttributeManager_6
    ATTR_TABLE = SET_TO join_id (uint8) = 1
    -> FeatureMerger [REQUESTOR]
ShortestPathFinder_2
    ALLOW_UTURNS = No
    REORDER_MODE = NONE
    SNAP_POINTS = Yes
    SNAP_TOLERANCE = 200
    THREE_D = No
    WEIGHT_ATTR_1 = @Value(forwardCost)
    WEIGHT_ATTR_2 = @Value(reverseCost)
    WEIGHT_ATTR_CHOICE = BY_TWO_ATTRIBUTES
    PATH -> Inspector_2
    PATH -> Bufferer_2
    PATH -> SpatialFilter_4 [Filter]
    PATH -> LengthCalculator_2
Inspector_2
Bufferer_2
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> poi_route_B (writer GEOJSON_2)
poi_route_B (writer GEOJSON_2)
    attributes: id string, lon float, lat float, _total_cost string, POI_ID int, LINK_ID int, TYPE string, POI_NAME string, ST_NAME string, LAT string, LON string, _predicate string
LengthCalculator_2
    DIM = 2
    LEN_ATTR = _length
    MULT = 1
    -> AttributeManager_4
AttributeManager_4
    ATTR_TABLE = SET_TO join_id (uint8) = 1
    -> FeatureMerger_2 [REQUESTOR]
Inspector_3
T2019_KAR_STREET_NODE (reader SHAPEFILE_3)
    attributes: NODE_ID long, LINK_ID long, POINT_NUM long, Z_LEVEL long, INTERSECT varchar(1), LAT number(31,15), LON number(31,15)
    -> Reprojector_3
Reprojector_3
    DEST = DHDN.Berlin/Cassini
    INTERPOLATION_TYPE = NearestNeighbor
    RASTER_CELL_SIZE = PreserveCells
    RASTER_TOLERANCE = 0.0
    REPROJECTED -> SpatialFilter_3 [Candidate]
    REPROJECTED -> SpatialFilter_4 [Candidate]
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    ATTR_ACCUM_MODE = None
    CALCULATION_MODE = NUMERIC
    FEAT_STATS = NODE_ID,NUMERIC_MODE,,,COUNT,SUM,MEAN,,,,,,,,
    SUMMARY -> AttributeManager_5
AttributeManager_5
    ATTR_TABLE = SET_TO join_id (uint8) = 1
    -> FeatureMerger [SUPPLIER]
FeatureMerger
    ATTR_ACCUM_MODE = Merge Supplier
    ATTR_CONFLICT_RES_LOOKUP = SUPPLIER_IF_CONFLICT
    IGNORE_NULLS = No
    JOIN_KEYS = @Value(join_id) @Value(join_id) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> route_A (writer GEODATABASE_FILE_1)
route_A (writer GEODATABASE_FILE_1)
    attributes: id char(5), lon float, lat float, _total_cost char(2048), _length double, join_id smallint, NODE_ID_total_count bigint, NODE_ID_sum double, NODE_ID_mean double
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
StatisticsCalculator_2
    ATTR_ACCUM_MODE = None
    CALCULATION_MODE = NUMERIC
    FEAT_STATS = NODE_ID,NUMERIC_MODE,,,COUNT,SUM,MEAN,,,,,,,,
    SUMMARY -> AttributeManager_3
AttributeManager_3
    ATTR_TABLE = SET_TO join_id (uint8) = 1
    -> FeatureMerger_2 [SUPPLIER]
FeatureMerger_2
    ATTR_ACCUM_MODE = Merge Supplier
    ATTR_CONFLICT_RES_LOOKUP = SUPPLIER_IF_CONFLICT
    IGNORE_NULLS = No
    JOIN_KEYS = @Value(join_id) @Value(join_id) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> route_B (writer GEODATABASE_FILE_2)
route_B (writer GEODATABASE_FILE_2)
    attributes: id char(5), lon float, lat float, _total_cost char(2048), _length double, join_id smallint, NODE_ID_total_count bigint, NODE_ID_sum double, NODE_ID_mean double
